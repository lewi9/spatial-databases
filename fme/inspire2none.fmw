FME workspace inspire2none.fmw

Parameters:
- SourceDataset_INSPIRE = C:\Users\Adam\Desktop\bdline_gml3_gb\Data\INSPIRE_AdministrativeUnit.gml   # Source INSPIRE File(s)
- FEATURE_TYPES = AdministrativeBoundary AdministrativeUnit Condominium NamedPlace SpatialDataSet
- SourceDataset_POSTGIS = Zadanie_2   # Connection
- DestDataset_POSTGIS = zadanie__3   # Connection

Readers:
- INSPIRE_1: INSPIRE from $(SourceDataset_INSPIRE) in EPSG:27700
- POSTGIS_1: POSTGIS from $(SourceDataset_POSTGIS)

Writers:
- POSTGIS_2: POSTGIS to $(DestDataset_POSTGIS)

Note: INSPIRE_AdministrativeUnit [INSPIRE] - GML file - takes less space on disk
AdministrativeBoundary (reader INSPIRE_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, geometry xml_geometry, inspireId.Identifier.localId xml_buffer, inspireId.Identifier.namespace xml_buffer,
      inspireId.Identifier.versionId xml_buffer, inspireId.Identifier.versionId.nilReason xml_buffer, inspireId.Identifier.versionId.xsi_nil xml_boolean, country.gco_nilReason xml_buffer, country.Country xml_buffer, country.Country.codeList xml_buffer, country.Country.codeListValue xml_buffer, country.Country.codeSpace xml_buffer, nationalLevel{}.owns xml_boolean, nationalLevel{}.nilReason xml_buffer, nationalLevel{}.gml_remoteSchema xml_buffer, nationalLevel{}.xlink_href xml_buffer, nationalLevel{}.xlink_role xml_buffer, nationalLevel{}.xlink_title xml_buffer, legalStatus xml_char(9), legalStatus.nilReason xml_buffer, legalStatus.xsi_nil xml_boolean, technicalStatus xml_char(14), technicalStatus.nilReason xml_buffer, technicalStatus.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, admUnit{}.owns xml_boolean, admUnit{}.nilReason xml_buffer, admUnit{}.gml_remoteSchema xml_buffer, admUnit{}.xlink_href xml_buffer,
      admUnit{}.xlink_role xml_buffer, admUnit{}.xlink_title xml_buffer, admUnit{}.xsi_nil xml_boolean, administeredBy{}.gml_remoteSchema xml_buffer, administeredBy{}.nilReason xml_buffer, administeredBy{}.owns xml_boolean, administeredBy{}.xlink_href xml_buffer, administeredBy{}.xlink_role xml_buffer, administeredBy{}.xlink_title xml_buffer, administeredBy{}.xsi_nil xml_boolean, boundary{}.gml_remoteSchema xml_buffer, boundary{}.nilReason xml_buffer, boundary{}.owns xml_boolean, boundary{}.xlink_href xml_buffer, boundary{}.xlink_role xml_buffer, boundary{}.xlink_title xml_buffer, boundary{}.xsi_nil xml_boolean, coAdminister{}.gml_remoteSchema xml_buffer, coAdminister{}.nilReason xml_buffer, coAdminister{}.owns xml_boolean, coAdminister{}.xlink_href xml_buffer, coAdminister{}.xlink_role xml_buffer, coAdminister{}.xlink_title xml_buffer, coAdminister{}.xsi_nil xml_boolean, condominium{}.gml_remoteSchema xml_buffer, condominium{}.nilReason xml_buffer, condominium{}.owns xml_boolean, condominium{}.xlink_href xml_buffer, condominium{}.xlink_role xml_buffer, condominium{}.xlink_title xml_buffer,
      condominium{}.xsi_nil xml_boolean, identifier.Identifier.localId xml_buffer, identifier.Identifier.namespace xml_buffer, identifier.Identifier.versionId xml_buffer, identifier.Identifier.versionId.nilReason xml_buffer, identifier.Identifier.versionId.xsi_nil xml_boolean, leastDetailedViewingResolution.MD_Resolution.distance.Distance xml_real64, leastDetailedViewingResolution.MD_Resolution.distance.Distance.uom xml_buffer, leastDetailedViewingResolution.MD_Resolution.distance.gco_nilReason xml_buffer, leastDetailedViewingResolution.MD_Resolution.equivalentScale.MD_RepresentativeFraction.denominator.Integer xml_int64, leastDetailedViewingResolution.MD_Resolution.equivalentScale.MD_RepresentativeFraction.denominator.gco_nilReason xml_buffer, leastDetailedViewingResolution.MD_Resolution.equivalentScale.MD_RepresentativeFraction.id xml_buffer, leastDetailedViewingResolution.MD_Resolution.equivalentScale.MD_RepresentativeFraction.uuid xml_buffer, leastDetailedViewingResolution.MD_Resolution.equivalentScale.gco_nilReason xml_buffer, leastDetailedViewingResolution.MD_Resolution.equivalentScale.uuidref xml_buffer, leastDetailedViewingResolution.MD_Resolution.equivalentScale.xlink_href xml_buffer, leastDetailedViewingResolution.MD_Resolution.equivalentScale.xlink_role xml_buffer, leastDetailedViewingResolution.MD_Resolution.equivalentScale.xlink_title xml_buffer, leastDetailedViewingResolution.nilReason xml_buffer, leastDetailedViewingResolution.owns xml_boolean, leastDetailedViewingResolution.xsi_nil xml_boolean, localType{}.LocalisedCharacterString xml_buffer, localType{}.LocalisedCharacterString.id xml_buffer, localType{}.LocalisedCharacterString.locale xml_buffer, localType{}.gco_nilReason xml_buffer, localType{}.uuidref xml_buffer, localType{}.xlink_href xml_buffer, localType{}.xlink_role xml_buffer, localType{}.xlink_title xml_buffer, localType{}.xsi_nil xml_boolean,
      lowerLevelUnit{}.gml_remoteSchema xml_buffer, lowerLevelUnit{}.nilReason xml_buffer, lowerLevelUnit{}.owns xml_boolean, lowerLevelUnit{}.xlink_href xml_buffer, lowerLevelUnit{}.xlink_role xml_buffer, lowerLevelUnit{}.xlink_title xml_buffer, lowerLevelUnit{}.xsi_nil xml_boolean, member{}.gml_remoteSchema xml_buffer, member{}.nilReason xml_buffer, member{}.owns xml_boolean, member{}.xlink_href xml_buffer, member{}.xlink_role xml_buffer, member{}.xlink_title xml_buffer, metadata xml_xml, metadata.gml_remoteSchema xml_buffer, metadata.nilReason xml_buffer, metadata.owns xml_boolean, metadata.xlink_href xml_buffer, metadata.xlink_role xml_buffer, metadata.xlink_title xml_buffer, metadata.xsi_nil xml_boolean, mostDetailedViewingResolution.MD_Resolution.distance.Distance xml_real64, mostDetailedViewingResolution.MD_Resolution.distance.Distance.uom xml_buffer, mostDetailedViewingResolution.MD_Resolution.distance.gco_nilReason xml_buffer, mostDetailedViewingResolution.MD_Resolution.equivalentScale.MD_RepresentativeFraction.denominator.Integer xml_int64, mostDetailedViewingResolution.MD_Resolution.equivalentScale.MD_RepresentativeFraction.denominator.gco_nilReason xml_buffer, mostDetailedViewingResolution.MD_Resolution.equivalentScale.MD_RepresentativeFraction.id xml_buffer, mostDetailedViewingResolution.MD_Resolution.equivalentScale.MD_RepresentativeFraction.uuid xml_buffer, mostDetailedViewingResolution.MD_Resolution.equivalentScale.gco_nilReason xml_buffer, mostDetailedViewingResolution.MD_Resolution.equivalentScale.uuidref xml_buffer,
      mostDetailedViewingResolution.MD_Resolution.equivalentScale.xlink_href xml_buffer, mostDetailedViewingResolution.MD_Resolution.equivalentScale.xlink_role xml_buffer, mostDetailedViewingResolution.MD_Resolution.equivalentScale.xlink_title xml_buffer, mostDetailedViewingResolution.nilReason xml_buffer, mostDetailedViewingResolution.owns xml_boolean, mostDetailedViewingResolution.xsi_nil xml_boolean, name{}.GeographicalName.grammaticalGender.gml_remoteSchema xml_buffer, name{}.GeographicalName.grammaticalGender.nilReason xml_buffer, name{}.GeographicalName.grammaticalGender.owns xml_boolean, name{}.GeographicalName.grammaticalGender.xlink_href xml_buffer, name{}.GeographicalName.grammaticalGender.xlink_role xml_buffer, name{}.GeographicalName.grammaticalGender.xlink_title xml_buffer, name{}.GeographicalName.grammaticalGender.xsi_nil xml_boolean, name{}.GeographicalName.grammaticalNumber.gml_remoteSchema xml_buffer, name{}.GeographicalName.grammaticalNumber.nilReason xml_buffer, name{}.GeographicalName.grammaticalNumber.owns xml_boolean, name{}.GeographicalName.grammaticalNumber.xlink_href xml_buffer, name{}.GeographicalName.grammaticalNumber.xlink_role xml_buffer, name{}.GeographicalName.grammaticalNumber.xlink_title xml_buffer, name{}.GeographicalName.grammaticalNumber.xsi_nil xml_boolean, name{}.GeographicalName.language xml_buffer, name{}.GeographicalName.language.nilReason xml_buffer, name{}.GeographicalName.language.xsi_nil xml_boolean, name{}.GeographicalName.nameStatus.gml_remoteSchema xml_buffer, name{}.GeographicalName.nameStatus.nilReason xml_buffer, name{}.GeographicalName.nameStatus.owns xml_boolean, name{}.GeographicalName.nameStatus.xlink_href xml_buffer, name{}.GeographicalName.nameStatus.xlink_role xml_buffer, name{}.GeographicalName.nameStatus.xlink_title xml_buffer, name{}.GeographicalName.nameStatus.xsi_nil xml_boolean,
      name{}.GeographicalName.nativeness.gml_remoteSchema xml_buffer, name{}.GeographicalName.nativeness.nilReason xml_buffer, name{}.GeographicalName.nativeness.owns xml_boolean, name{}.GeographicalName.nativeness.xlink_href xml_buffer, name{}.GeographicalName.nativeness.xlink_role xml_buffer, name{}.GeographicalName.nativeness.xlink_title xml_buffer, name{}.GeographicalName.nativeness.xsi_nil xml_boolean, name{}.GeographicalName.pronunciation.PronunciationOfName.pronunciationIPA xml_buffer, name{}.GeographicalName.pronunciation.PronunciationOfName.pronunciationIPA.nilReason xml_buffer, name{}.GeographicalName.pronunciation.PronunciationOfName.pronunciationIPA.xsi_nil xml_boolean, name{}.GeographicalName.pronunciation.PronunciationOfName.pronunciationSoundLink xml_buffer, name{}.GeographicalName.pronunciation.PronunciationOfName.pronunciationSoundLink.nilReason xml_buffer, name{}.GeographicalName.pronunciation.PronunciationOfName.pronunciationSoundLink.xsi_nil xml_boolean, name{}.GeographicalName.pronunciation.nilReason xml_buffer, name{}.GeographicalName.pronunciation.xsi_nil xml_boolean, name{}.GeographicalName.sourceOfName xml_buffer, name{}.GeographicalName.sourceOfName.nilReason xml_buffer, name{}.GeographicalName.sourceOfName.xsi_nil xml_boolean, name{}.GeographicalName.spelling{}.SpellingOfName.script xml_buffer, name{}.GeographicalName.spelling{}.SpellingOfName.script.nilReason xml_buffer, name{}.GeographicalName.spelling{}.SpellingOfName.script.xsi_nil xml_boolean, name{}.GeographicalName.spelling{}.SpellingOfName.text xml_buffer, name{}.GeographicalName.spelling{}.SpellingOfName.transliterationScheme xml_buffer, name{}.GeographicalName.spelling{}.SpellingOfName.transliterationScheme.nilReason xml_buffer, name{}.GeographicalName.spelling{}.SpellingOfName.transliterationScheme.xsi_nil xml_boolean, name{}.nilReason xml_buffer, name{}.xsi_nil xml_boolean, nationalCode xml_buffer, nationalLevel.gml_remoteSchema xml_buffer, nationalLevel.nilReason xml_buffer,
      nationalLevel.owns xml_boolean, nationalLevel.xlink_href xml_buffer, nationalLevel.xlink_role xml_buffer, nationalLevel.xlink_title xml_buffer, nationalLevelName{}.LocalisedCharacterString xml_buffer, nationalLevelName{}.LocalisedCharacterString.id xml_buffer, nationalLevelName{}.LocalisedCharacterString.locale xml_buffer, nationalLevelName{}.gco_nilReason xml_buffer, nationalLevelName{}.uuidref xml_buffer, nationalLevelName{}.xlink_href xml_buffer, nationalLevelName{}.xlink_role xml_buffer, nationalLevelName{}.xlink_title xml_buffer, nationalLevelName{}.xsi_nil xml_boolean, relatedSpatialObject{}.Identifier.localId xml_buffer, relatedSpatialObject{}.Identifier.namespace xml_buffer, relatedSpatialObject{}.Identifier.versionId xml_buffer, relatedSpatialObject{}.Identifier.versionId.nilReason xml_buffer, relatedSpatialObject{}.Identifier.versionId.xsi_nil xml_boolean, relatedSpatialObject{}.nilReason xml_buffer, relatedSpatialObject{}.xsi_nil xml_boolean, residenceOfAuthority{}.ResidenceOfAuthority.geometry xml_geometry, residenceOfAuthority{}.ResidenceOfAuthority.name.GeographicalName.grammaticalGender.gml_remoteSchema xml_buffer, residenceOfAuthority{}.ResidenceOfAuthority.name.GeographicalName.grammaticalGender.nilReason xml_buffer, residenceOfAuthority{}.ResidenceOfAuthority.name.GeographicalName.grammaticalGender.owns xml_boolean, residenceOfAuthority{}.ResidenceOfAuthority.name.GeographicalName.grammaticalGender.xlink_href xml_buffer, residenceOfAuthority{}.ResidenceOfAuthority.name.GeographicalName.grammaticalGender.xlink_role xml_buffer, residenceOfAuthority{}.ResidenceOfAuthority.name.GeographicalName.grammaticalGender.xlink_title xml_buffer, residenceOfAuthority{}.ResidenceOfAuthority.name.GeographicalName.grammaticalGender.xsi_nil xml_boolean, residenceOfAuthority{}.ResidenceOfAuthority.name.GeographicalName.grammaticalNumber.gml_remoteSchema xml_buffer, residenceOfAuthority{}.ResidenceOfAuthority.name.GeographicalName.grammaticalNumber.nilReason xml_buffer,
      residenceOfAuthority{}.ResidenceOfAuthority.name.GeographicalName.grammaticalNumber.owns xml_boolean, residenceOfAuthority{}.ResidenceOfAuthority.name.GeographicalName.grammaticalNumber.xlink_href xml_buffer, residenceOfAuthority{}.ResidenceOfAuthority.name.GeographicalName.grammaticalNumber.xlink_role xml_buffer, residenceOfAuthority{}.ResidenceOfAuthority.name.GeographicalName.grammaticalNumber.xlink_title xml_buffer, residenceOfAuthority{}.ResidenceOfAuthority.name.GeographicalName.grammaticalNumber.xsi_nil xml_boolean, residenceOfAuthority{}.ResidenceOfAuthority.name.GeographicalName.language xml_buffer, residenceOfAuthority{}.ResidenceOfAuthority.name.GeographicalName.language.nilReason xml_buffer, residenceOfAuthority{}.ResidenceOfAuthority.name.GeographicalName.language.xsi_nil xml_boolean, residenceOfAuthority{}.ResidenceOfAuthority.name.GeographicalName.nameStatus.gml_remoteSchema xml_buffer, residenceOfAuthority{}.ResidenceOfAuthority.name.GeographicalName.nameStatus.nilReason xml_buffer, residenceOfAuthority{}.ResidenceOfAuthority.name.GeographicalName.nameStatus.owns xml_boolean, residenceOfAuthority{}.ResidenceOfAuthority.name.GeographicalName.nameStatus.xlink_href xml_buffer, residenceOfAuthority{}.ResidenceOfAuthority.name.GeographicalName.nameStatus.xlink_role xml_buffer, residenceOfAuthority{}.ResidenceOfAuthority.name.GeographicalName.nameStatus.xlink_title xml_buffer, residenceOfAuthority{}.ResidenceOfAuthority.name.GeographicalName.nameStatus.xsi_nil xml_boolean, residenceOfAuthority{}.ResidenceOfAuthority.name.GeographicalName.nativeness.gml_remoteSchema xml_buffer, residenceOfAuthority{}.ResidenceOfAuthority.name.GeographicalName.nativeness.nilReason xml_buffer, residenceOfAuthority{}.ResidenceOfAuthority.name.GeographicalName.nativeness.owns xml_boolean, residenceOfAuthority{}.ResidenceOfAuthority.name.GeographicalName.nativeness.xlink_href xml_buffer, residenceOfAuthority{}.ResidenceOfAuthority.name.GeographicalName.nativeness.xlink_role xml_buffer, residenceOfAuthority{}.ResidenceOfAuthority.name.GeographicalName.nativeness.xlink_title xml_buffer, residenceOfAuthority{}.ResidenceOfAuthority.name.GeographicalName.nativeness.xsi_nil xml_boolean, residenceOfAuthority{}.ResidenceOfAuthority.name.GeographicalName.pronunciation.PronunciationOfName.pronunciationIPA xml_buffer, residenceOfAuthority{}.ResidenceOfAuthority.name.GeographicalName.pronunciation.PronunciationOfName.pronunciationIPA.nilReason xml_buffer, residenceOfAuthority{}.ResidenceOfAuthority.name.GeographicalName.pronunciation.PronunciationOfName.pronunciationIPA.xsi_nil xml_boolean, residenceOfAuthority{}.ResidenceOfAuthority.name.GeographicalName.pronunciation.PronunciationOfName.pronunciationSoundLink xml_buffer, residenceOfAuthority{}.ResidenceOfAuthority.name.GeographicalName.pronunciation.PronunciationOfName.pronunciationSoundLink.nilReason xml_buffer, residenceOfAuthority{}.ResidenceOfAuthority.name.GeographicalName.pronunciation.PronunciationOfName.pronunciationSoundLink.xsi_nil xml_boolean, residenceOfAuthority{}.ResidenceOfAuthority.name.GeographicalName.pronunciation.nilReason xml_buffer, residenceOfAuthority{}.ResidenceOfAuthority.name.GeographicalName.pronunciation.xsi_nil xml_boolean,
      residenceOfAuthority{}.ResidenceOfAuthority.name.GeographicalName.sourceOfName xml_buffer, residenceOfAuthority{}.ResidenceOfAuthority.name.GeographicalName.sourceOfName.nilReason xml_buffer, residenceOfAuthority{}.ResidenceOfAuthority.name.GeographicalName.sourceOfName.xsi_nil xml_boolean, residenceOfAuthority{}.ResidenceOfAuthority.name.GeographicalName.spelling{}.SpellingOfName.script xml_buffer, residenceOfAuthority{}.ResidenceOfAuthority.name.GeographicalName.spelling{}.SpellingOfName.script.nilReason xml_buffer, residenceOfAuthority{}.ResidenceOfAuthority.name.GeographicalName.spelling{}.SpellingOfName.script.xsi_nil xml_boolean, residenceOfAuthority{}.ResidenceOfAuthority.name.GeographicalName.spelling{}.SpellingOfName.text xml_buffer, residenceOfAuthority{}.ResidenceOfAuthority.name.GeographicalName.spelling{}.SpellingOfName.transliterationScheme xml_buffer, residenceOfAuthority{}.ResidenceOfAuthority.name.GeographicalName.spelling{}.SpellingOfName.transliterationScheme.nilReason xml_buffer, residenceOfAuthority{}.ResidenceOfAuthority.name.GeographicalName.spelling{}.SpellingOfName.transliterationScheme.xsi_nil xml_boolean, residenceOfAuthority{}.nilReason xml_buffer, residenceOfAuthority{}.xsi_nil xml_boolean, type{}.gml_remoteSchema xml_buffer, type{}.nilReason xml_buffer, type{}.owns xml_boolean, type{}.xlink_href xml_buffer, type{}.xlink_role xml_buffer, type{}.xlink_title xml_buffer, type{}.xsi_nil xml_boolean, upperLevelUnit.gml_remoteSchema xml_buffer, upperLevelUnit.nilReason xml_buffer, upperLevelUnit.owns xml_boolean, upperLevelUnit.xlink_href xml_buffer, upperLevelUnit.xlink_role xml_buffer, upperLevelUnit.xlink_title xml_buffer, upperLevelUnit.xsi_nil xml_boolean
    -> Tester
Note: I know that this is not what is in task description, but I believe that I have learned more (reading documentation of dataset, about inspire, looking how to find the South Wale etc.)
Note: There is no 2rdOrder to get South Wale - so get Walish regions
Tester
    BOOL_OP = OR
    TEST_CLAUSE = CASE_INSENSITIVE_TEST @Value(nationalCode) LIKE W%
    TEST_MODE = TEST
    PASSED -> HTTPCaller
Note: HTTPCaller to scrap page about region - return code 200, but the linked data service has now been withdrawn so there is no needed data...
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(gml_identifier)
    TRANSFER_TIMEOUT_LENGTH = 90
    UPLOAD_CONTENT_TYPE = Text (text/plain)
    UPLOAD_TYPE = Specify Upload Body
    USE_COOKIES = No
    VERIFY_SSL_CERTIFICATES = Yes
    -> Aggregator
Note: Drop features - there is no need to hold them
Aggregator
    ACCUM_ATTRS_NAME = Drop Incoming Attributes
    AGGREGATE_TYPE = Homogeneous Collection (If Possible)
    MODE = Geometry - Assemble One Level
    SEP = ,
    AGGREGATE -> Reprojector
Note: Transform to unify coordinate system
Reprojector
    DEST = LL-WGS84
    INTERPOLATION_TYPE_NAME = Nearest Neighbor
    RASTER_CELL_SIZE = Preserve Cells
    RASTER_TOLERANCE = 0.0
    REPROJECTED -> Clipper [CLIPPER]
Note: Read from table (they are not rasters, but my pc process them so long, I will go with geometry, the rule is the same)
Extents (reader POSTGIS_1)
    attributes: newname varchar(200)
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Exports (writer POSTGIS_2)
Note: Drop and create table
Exports (writer POSTGIS_2)
    attributes: newname varchar(200)
